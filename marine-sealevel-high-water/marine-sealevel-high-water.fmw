FME workspace marine-sealevel-high-water.fmw

Parameters:
- DestDataset_HYPER =

Writers:
- HYPER_1: HYPER to $(DestDataset_HYPER)

Creator
    GEOMTYPE = Geometry Object
    NUM = 1
    CREATED -> HTTPCaller
    CREATED -> FeatureReader [INITIATOR]
    CREATED -> FeatureReader_2 [INITIATOR]
Note: Extract Metadata
HTTPCaller
    CONNECTION_TIMEOUT_LENGTH = 60
    ERROR_ATTR = _error
    FOLLOW_REDIRECTS = FOLLOW_WITH_GET
    HTTP_METHOD = POST
    MAX_HTTP_VERSION = HTTP_2
    MAX_TRANSFERS_IN_PROGRESS = 25
    REDIRECT_AUTH = ORIGINAL_DOMAIN_ONLY
    SAVE_FILE = Attribute
    STATUS_CODE_ATTR = _http_status_code
    TARGET_ATTR = _response_body
    TARGET_ATTR_ENCODING = auto-detect
    TARGET_URL = https://cds.climate.copernicus.eu/workflows/c3s/hidden-app-marine-sealevel-detail-web/cf526b99554c366c8d911b82c48f82e9ff859bfc/workflow
    TRANSFER_TIMEOUT_LENGTH = 90
    UPLOAD_BODY = {"indicator":"annual_highest_high_water_level"}
    UPLOAD_CONTENT_TYPE = JSON (application/json)
    UPLOAD_TYPE = Specify Upload Body
    USE_COOKIES = No
    VERIFY_SSL_CERTIFICATES = Yes
    -> JSONFragmenter
Note: Extract the provided GeoJSON
FeatureReader
    ATTRIBUTES = livemap.plot-1620724866.9640718-14813-20-57195c1e-6b93-49f5-ae05-27553a1448e1,"id,featurecla,name,namealt,changed,note,name_fr,min_label,max_label,scalerank,label,wikidataid,name_ar,name_bn,name_de,name_en,name_es,name_el,name_hi,name_hu,name_id,name_it,name_ja,name_ko,name_nl,name_pl,name_pt,name_ru,name_sv,name_tr,name_vi,name_zh,wdid_score,ne_id,no_data_value,value,style.fillColor,style.fillOpacity,style_selected.fillColor,style_selected.fillOpacity"
    ATTR_ACCUM_MODE = Merge Initiator and Result
    ATTR_CONFLICT_RES = Use Result
    ATTR_IGNORE_NULLS = No
    COMBINE_GEOM = Use Result
    DATASET = https://download-0001.copernicus-climate.eu/cache-compute-0001/cache/publicapps/livemap.plot-1620724866.9640718-14813-20-57195c1e-6b93-49f5-ae05-27553a1448e1.geojson
    FORMAT = GEOJSON
    GEOJSON_FLATTEN_MODE = ALL_LEVELS
    GEOJSON_USE_BASENAME_AS_DEFAULT_FEATURE_TYPE = Yes
    GEOJSON_USE_SEARCH_ENVELOPE = NO
    INTERACT = NONE
    OUTPUT_FEATURES_DISPLAY = Schema and Data Features
    livemap.plot-1620724866.9640718-14813-20-57195c1e-6b93-49f5-ae05-27553a1448e1 -> AttributeRemover
AttributeRemover
    REMOVE_ATTRS = name_ar,name_bn,name_de,name_el,name_en,name_es,name_fr,name_hi,name_hu,name_id,name_it,name_ja,name_ko,name_nl,name_pl,name_pt,name_ru,name_sv,name_tr,name_vi,name_zh,no_data_value
    -> marine-sealevel (writer HYPER_1)
marine-sealevel (writer HYPER_1)
    attributes: _creation_instance text, id text, featurecla text, name text, namealt text, changed text, note text, min_label double, max_label double, scalerank bigint, label text, wikidataid text, wdid_score bigint, ne_id bigint, value double, style.fillColor text, style.fillOpacity bigint, style_selected.fillColor text, style_selected.fillOpacity bigint
Note: Extract the provided GeoJSON
FeatureReader_2
    ATTRIBUTES = livemap.plot-1620724867.5549395-14813-21-57195c1e-6b93-49f5-ae05-27553a1448e1,"id,NUTS_ID,LEVL_CODE,CNTR_CODE,NAME_LATN,NUTS_NAME,MOUNT_TYPE,URBN_TYPE,COAST_TYPE,FID,style.color,style.fillColor,style.fillOpacity,style.weight,style_selected.color,style_selected.fillColor,style_selected.fillOpacity,style_selected.weight,name"
    ATTR_ACCUM_MODE = Merge Initiator and Result
    ATTR_CONFLICT_RES = Use Result
    ATTR_IGNORE_NULLS = No
    COMBINE_GEOM = Use Result
    DATASET = https://download-0001.copernicus-climate.eu/cache-compute-0001/cache/publicapps/livemap.plot-1620724867.5549395-14813-21-57195c1e-6b93-49f5-ae05-27553a1448e1.geojson
    FORMAT = GEOJSON
    GEOJSON_FLATTEN_MODE = ALL_LEVELS
    GEOJSON_USE_BASENAME_AS_DEFAULT_FEATURE_TYPE = Yes
    GEOJSON_USE_SEARCH_ENVELOPE = NO
    INTERACT = NONE
    OUTPUT_FEATURES_DISPLAY = Schema and Data Features
    livemap.plot-1620724867.5549395-14813-21-57195c1e-6b93-49f5-ae05-27553a1448e1 -> AttributeRemover_3
AttributeRemover_3
    REMOVE_ATTRS = name_ar,name_bn,name_de,name_el,name_en,name_es,name_fr,name_hi,name_hu,name_id,name_it,name_ja,name_ko,name_nl,name_pl,name_pt,name_ru,name_sv,name_tr,name_vi,name_zh,no_data_value
    -> country (writer HYPER_1)
country (writer HYPER_1)
    attributes: _creation_instance text, id text, NUTS_ID text, LEVL_CODE bigint, CNTR_CODE text, NAME_LATN text, NUTS_NAME text, MOUNT_TYPE bigint, URBN_TYPE bigint, COAST_TYPE bigint, FID text, style.color text, style.fillColor text, style.fillOpacity bigint, style.weight bigint, style_selected.color text, style_selected.fillColor text, style_selected.fillOpacity bigint, style_selected.weight bigint, name text

Bookmark: GET GeoJSON URL's
JSONFragmenter
    EXPLODE_FORMAT = JSON
    EXTRACT_ATTR = No
    JSON_ATTR = _response_body
    JSON_QUERY = json["results"]
    READ_FROM_FILE = NO
    REJECT_EMPTY_LISTS = YES
    FRAGMENTS -> JSONFragmenter_2
JSONFragmenter_2
    EXPLODE_FORMAT = JSON
    EXTRACT_ATTR = No
    JSON_ATTR = _response_body
    JSON_QUERY = json[0]["layers"]
    READ_FROM_FILE = NO
    REJECT_EMPTY_LISTS = YES
    FRAGMENTS -> JSONFragmenter_3
JSONFragmenter_3
    EXPLODE_FORMAT = JSON
    EXTRACT_ATTR = No
    JSON_ATTR = _response_body
    JSON_QUERY = json[*]
    READ_FROM_FILE = NO
    REJECT_EMPTY_LISTS = YES
    FRAGMENTS -> JSONExtractor
JSONExtractor
    EXTRACT_QUERY_TABLE = geoJson json["geojson_data_source"]
    JSON_DOCUMENT = @Value(_response_body)
    READ_FROM_FILE = NO
    EVALUATED -> AttributeRemover_2
AttributeRemover_2
    REMOVE_ATTRS = _creation_instance,_http_status_code,_response_body,json_index,json_type
    -> TestFilter
TestFilter
    DEFAULT_VALUE = <UNFILTERED>
    TEST_LIST = "BOOL_OP,OR,COMPOSITE_TEST,""""""1"""""",TEST_CLAUSE,TEST geoJson ATTRIBUTE_HAS_A_VALUE """,GeoJSON
    GeoJSON -> Aggregator
Aggregator
    ACCUM_ATTRS_NAME = Drop Incoming Attributes
    GROUP_BY = geoJson
    MODE = Attributes Only
    SEP = ,
