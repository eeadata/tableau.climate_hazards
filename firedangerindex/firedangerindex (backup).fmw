FME workspace firedangerindex (backup).fmw
Description: Climate Hazard harvesting script
Usage: The following website is currently used to harvest the data.
        https://c3s.maris.nl/health/climatic-suitability-of-tiger-mosquito--season-length-detail.html
This website has some background scripts (Python) that extracts the data out of (I think images) based on the NUTS levels. These can then be downloaded as a CSV.
I reverse engineered how this worked using the Chrome developer extension.
It performs the job in two processess.
1. Download the files from the website and store them locally. (Remove the files if you wish to refresh the content)
2. Produce one single .csv from the final result.
History: 15/04/2021,Jan Bliki,Initiation

Parameters:
- URL = https://cds.climate.copernicus.eu/workflows/c3s/hidden-app-firedangerindex-detail-web/2719f6635f6c0294122d8b989f62e5e4ffb0ca12/workflow   # WebService
- TargetCSVName = firedangerindex   # Target dataset file name
- TempStoragePath = Files   # Temp storage
- DestDataset_CSV2 = ../Output   # Destination CSV (Comma Separated Value) Folder

Writers:
- CSV2_1: CSV2 to $(DestDataset_CSV2)

Creator
    GEOMTYPE = Geometry Object
    NUM = 1
    CREATED -> AttributeCreator_3
AttributeCreator_3
    ATTR_TABLE = SET_TO join = 1
    -> MakeFeaturesFromAttribute_2
    -> MakeFeaturesFromAttribute_3
    -> MakeFeaturesFromAttribute_4
Note: Data scraper for https://c3s.maris.nl/health/ / Will download all possible datasets from the website as it was designed in 04/2021. / Steps : / 1: Check the website you want to harvest and memic all the filters (Time period, Season, Scenarios,...) / 2: Fit the JSON with the website in AttributeCreator 11 / 3: Change the filename for the individual files in Attribute 10 / 4: Change the publish parameters (URL + TargetCSVName)
FeatureJoiner
    ATTR_CONFLICT_RES = Use Left
    GEOMETRY_HANDLING = Use Left
    JOIN_KEYS = join join AUTO
    JOIN_MODE = Full
    JOINED -> FeatureJoiner_2 [LEFT]
FeatureJoiner_2
    ATTR_CONFLICT_RES = Use Left
    GEOMETRY_HANDLING = Use Left
    JOIN_KEYS = join join AUTO
    JOIN_MODE = Full
    JOINED -> AttributeRemover_4
AttributeRemover_4
    REMOVE_ATTRS = join
    -> Sorter
Sorter
    SORT_PARM = TimePeriod ALPHA ASCENDING Scenario ALPHA ASCENDING NutsLevel NUMERIC ASCENDING
    SORTED -> AttributeRemover_2
AttributeRemover_2
    REMOVE_ATTRS = _creation_instance
    -> AttributeCreator_11
Note: AttributeCreator_11 [AttributeCreator] / Attributes To Create: New AttributeAttribute ValueclimateJson{"rcp":"@Value(Scenario)","period":"@Value(TimePeriod)","nutslevel":"@Value(NutsLevel)"}
Note: The JSON the webservice needs to produce the export data...
AttributeCreator_11
    ATTR_TABLE = SET_TO climateJson = {"rcp":"@Value(Scenario)","period":"@Value(TimePeriod)","nutslevel":"@Value(NutsLevel)"}
    -> AttributeCreator_10
Note: AttributeCreator_10 [AttributeCreator] / Attributes To Create: New AttributeAttribute ValuecsvFile$(TempStoragePath)/@Value(TimePeriod)_@Value(Scenario)_@Value(NutsLevel).csv
Note: FileNameBasedOnParams
AttributeCreator_10
    ATTR_TABLE = SET_TO csvFile = $(TempStoragePath)/@Value(TimePeriod)_@Value(Scenario)_@Value(NutsLevel).csv
    -> FileExistenceChecker
FeatureJoiner_3
    ATTR_CONFLICT_RES = Use Left
    GEOMETRY_HANDLING = Use Left
    JOIN_KEYS = NutsCode NUTS_ID STRING
    JOIN_MODE = Left
    JOINED -> AttributeRemover_7
AttributeRemover_7
    REMOVE_ATTRS = LEVL_CODE,NUTS_ID,_downloaddata,_http_status_code,_response_file_path,climateJson
    -> agriculturetmean (writer CSV2_1)
agriculturetmean (writer CSV2_1)
    attributes: NutsCode string, Value string, csvFile string, TimePeriod string, Scenario string, NutsLevel string, FullName string
Note: For testing
Sampler
    RATE = 5
    SAMPLE_MODE = No
    SAMPLE_TYPE_LONG = First N Features

Bookmark: Time Periods
MakeFeaturesFromAttribute_2
    FEATERLIST = 2006-2035,2036-2065,2066-2095
    MATCHED_RESULT_ATTR = TimePeriod
    -> FeatureJoiner [LEFT]

Bookmark: Scenarios
MakeFeaturesFromAttribute_3
    FEATERLIST = RCP2.6,RCP4.5,RCP8.5
    MATCHED_RESULT_ATTR = Scenario
    -> FeatureJoiner [RIGHT]

Bookmark: Nuts level
MakeFeaturesFromAttribute_4
    FEATERLIST = National level (NUTS0),First sub-national level (NUTS1),Second sub-national level (NUTS2)
    MATCHED_RESULT_ATTR = NutsLevel
    -> FeatureJoiner_2 [RIGHT]

Bookmark: GET DATA FROM COPERNICUS AND STORE AS FILE
Note: Only ask for the file if we don't have it on our file system.
FileExistenceChecker
    Input = @Value(csvFile)
    Exists -> HTTPCaller_Output
    DoesNotExist -> c3sReader
Note: The Magic happens here / This script is the reversed engineerd bit.
c3sReader
    JSON = @Value(climateJson)
    URL = $(URL)
    -> HTTPCaller
Note: Save to temp
HTTPCaller
    CONNECTION_TIMEOUT_LENGTH = 60
    ERROR_ATTR = _error
    FILE_PATH_ATTR = _response_file_path
    FOLLOW_REDIRECTS = FOLLOW_WITH_GET
    HTTP_METHOD = GET
    OUTPUT_FILENAME = @Value(csvFile)
    REDIRECT_AUTH = ORIGINAL_DOMAIN_ONLY
    SAVE_FILE = File
    SAVE_MULTI = No
    STATUS_CODE_ATTR = _http_status_code
    TARGET_URL = @Value(_downloaddata)
    TRANSFER_TIMEOUT_LENGTH = 90
    USE_COOKIES = No
    VERIFY_SSL_CERTIFICATES = Yes
    -> HTTPCaller_Output
HTTPCaller_Output: Logger
    LOG_FEATURE = LOG_ONLY
    MAXCOORDS = 20
    MAXFEATS = 20
    MESSAGE = Feature is:
    SEVERITY = INFO
    LOGGED -> AttributeRemover_5

Bookmark: STORE INTO ONE SINGLE CSV FILE
AttributeRemover_5
    REMOVE_ATTRS = _Steps
    -> FeatureReader [INITIATOR]
    -> Sampler_2
FeatureReader
    ATTRS_TO_EXPOSE = col0 col1
    ATTR_ACCUM_MODE = Merge Initiator and Result
    ATTR_CONFLICT_RES = Use Result
    ATTR_IGNORE_NULLS = No
    COMBINE_GEOM = Use Result
    CSV2_CASE_SENSITIVE_FIELD_NAMES = Yes
    CSV2_CHUNK_SIZE = 100000
    CSV2_DATA_START_LINE = 1
    CSV2_DELIMITER = ,
    CSV2_ENCODING = UTF-8
    CSV2_ENFORCE_STRICT_SCHEMA = No
    CSV2_FEATURE_TYPE_NAME = FORMAT_NAME
    CSV2_FIELD_QUALIFIER_CHARACTER = "
    CSV2_FIELD_QUALIFIER_ESCAPE_CHARACTER = "
    CSV2_PRESERVE_SOURCE_ENCODING = No
    CSV2_QUERY_FEATURE_TYPES_FOR_MERGE_FILTERS = Yes
    CSV2_READ_EMPTY_VALUES_AS = Null
    CSV2_READ_SKIPPED_LINES = No
    CSV2_SCAN_ADDITIONAL_FIELDS = No
    CSV2_SCAN_MAX_ROWS = 10000
    CSV2_SCAN_TYPES = Yes
    CSV2_SKIP_DUPLICATE_DELIMITERS = No
    CSV2_TRIM_FEATURE_TYPE_NAME = Yes
    CSV2_TRIM_FIELD_NAME_QUALIFIERS = Yes
    CSV2_TRIM_FIELD_NAME_WHITESPACE = Yes
    CSV2_TRIM_FIELD_VALUE_QUALIFIERS = Yes
    CSV2_USE_CUSTOM_SCHEMA = YES
    DATASET = @Value(csvFile)
    FORMAT = CSV2
    INTERACT = <No Spatial Filter>
    OUTPUT_FEATURES_DISPLAY = Data Features
    <OTHER> -> AttributeRenamer
AttributeRenamer
    ATTR_TABLE:
      RENAME_SET_DEFAULT col0 > NutsCode
      RENAME_SET_DEFAULT col1 > Value
    -> FeatureJoiner_3 [LEFT]

Bookmark: NUTS LAYERS NAME EXTRACTION
Sampler_2
    RATE = 1
    SAMPLE_MODE = No
    SAMPLE_TYPE_LONG = First N Features
    SAMPLED -> FeatureReader_2 [INITIATOR]
FeatureReader_2
    ATTRIBUTES = NUTS_LB_2021_3857_LEVL_0,"NUTS_ID,LEVL_CODE,CNTR_CODE,NAME_LATN,NUTS_NAME,MOUNT_TYPE,URBN_TYPE,COAST_TYPE,FID",NUTS_LB_2021_3857_LEVL_1,"NUTS_ID,LEVL_CODE,CNTR_CODE,NAME_LATN,NUTS_NAME,MOUNT_TYPE,URBN_TYPE,COAST_TYPE,FID",NUTS_LB_2021_3857_LEVL_2,"NUTS_ID,LEVL_CODE,CNTR_CODE,NAME_LATN,NUTS_NAME,MOUNT_TYPE,URBN_TYPE,COAST_TYPE,FID",NUTS_LB_2021_3857_LEVL_3,"NUTS_ID,LEVL_CODE,CNTR_CODE,NAME_LATN,NUTS_NAME,MOUNT_TYPE,URBN_TYPE,COAST_TYPE,FID"
    ATTR_ACCUM_MODE = Only Use Result
    COMBINE_GEOM = Use Result
    COORDSYS = EPSG:3857
    DATASET = ""/Users/janbliki/Documents/FME/Nuts/NUTS_LB_2021_3857_LEVL_1.shp.zip[*.shp]" "/Users/janbliki/Documents/FME/Nuts/NUTS_LB_2021_3857_LEVL_2.shp.zip[*.shp]" "/Users/janbliki/Documents/FME/Nuts/NUTS_LB_2021_3857_LEVL_3.shp.zip[*.shp]" "/Users/janbliki/Documents/FME/Nuts/NUTS_LB_2021_3857_LEVL_0.shp.zip[*.shp]""
    FORMAT = SHAPEFILE
    INTERACT = <No Spatial Filter>
    OUTPUT_FEATURES_DISPLAY = Schema and Data Features
    SHAPEFILE_DONUT_DETECTION = ORIENTATION
    SHAPEFILE_ENCODING = fme-source-encoding
    SHAPEFILE_MEASURES_AS_Z = No
    SHAPEFILE_NUMERIC_TYPE_ATTRIBUTE_HANDLING = STANDARD_TYPES
    SHAPEFILE_READ_BLANK_AS = MISSING
    SHAPEFILE_REPORT_BAD_GEOMETRY = No
    SHAPEFILE_TRIM_PRECEDING_SPACES = Yes
    SHAPEFILE_USE_SEARCH_ENVELOPE = NO
    NUTS_LB_2021_3857_LEVL_0 -> GeometryRemover
    NUTS_LB_2021_3857_LEVL_1 -> GeometryRemover
    NUTS_LB_2021_3857_LEVL_2 -> GeometryRemover
    NUTS_LB_2021_3857_LEVL_3 -> GeometryRemover
GeometryRemover
    -> AttributeRenamer_2
AttributeRenamer_2
    ATTR_TABLE = RENAME_SET_DEFAULT NUTS_NAME > FullName
    -> AttributeRemover_6
AttributeRemover_6
    REMOVE_ATTRS = CNTR_CODE,COAST_TYPE,FID,MOUNT_TYPE,NAME_LATN,URBN_TYPE
    -> FeatureJoiner_3 [RIGHT]

FME custom transformer c3sReader
Transformer that is able to communicate with the Copernicus webservice.

Parameters:
- URL =   # WebService
- JSON =   # " " JSON For Service

Input (input)
    -> AttributeCreator
Note: Produce JSON snipped and take URL from parameter.
AttributeCreator
    ATTR_TABLE:
      SET_TO PostJson = $(JSON)
      SET_TO URl = $(URL)
    -> StringLengthCalculator
Note: The server expects to receive the total length of the JSON file send.
StringLengthCalculator
    LENGTH_ATTR = _JsonLength
    SRC_ATTR = PostJson
    -> ExpressionEvaluator
    -> HTTPCaller_3
Note: Sen an OPTION method. I think this is acting as the reset on the server.
HTTPCaller_3
    CONNECTION_TIMEOUT_LENGTH = 60
    CUSTOM_HEADERS = accept;*/* access-control-request-headers;content-type access-control-request-method;POST
    ERROR_ATTR = _error
    FOLLOW_REDIRECTS = FOLLOW_WITH_GET
    HTTP_METHOD = OPTIONS
    REDIRECT_AUTH = ORIGINAL_DOMAIN_ONLY
    SAVE_FILE = Attribute
    STATUS_CODE_ATTR = _http_status_code
    TARGET_ATTR = _response_body
    TARGET_ATTR_ENCODING = auto-detect
    TARGET_URL = @Value(URl)
    TRANSFER_TIMEOUT_LENGTH = 90
    USE_COOKIES = No
    VERIFY_SSL_CERTIFICATES = Yes
    -> HTTPCaller
Note: Send the JSON File using a POST Method.
HTTPCaller
    CONNECTION_TIMEOUT_LENGTH = 180
    CUSTOM_HEADERS = accept;application/json authority;cds.climate.copernicus.eu content-length;@Value(_JsonLength) origin;https://climate-adapt.eea.europa.eu referer;https://climate-adapt.eea.europa.eu/
    ERROR_ATTR = _error
    FOLLOW_REDIRECTS = FOLLOW_WITH_GET
    HTTP_METHOD = POST
    REDIRECT_AUTH = ORIGINAL_DOMAIN_ONLY
    SAVE_FILE = Attribute
    STATUS_CODE_ATTR = _http_status_code
    TARGET_ATTR = _response_body
    TARGET_ATTR_ENCODING = auto-detect
    TARGET_URL = @Value(URl)
    TRANSFER_TIMEOUT_LENGTH = 200
    UPLOAD_BODY = @Value(PostJson)
    UPLOAD_CONTENT_TYPE = JSON (application/json)
    UPLOAD_TYPE = Specify Upload Body
    USE_COOKIES = No
    VERIFY_SSL_CERTIFICATES = Yes
    -> JSONExtractor
Note: The server should come back with a queue identifier. / This is a async process and we are expected to poll if the job has been performed.
JSONExtractor
    EXTRACT_QUERY_TABLE = queue JSON["queue"]
    JSON_DOCUMENT = @Value(_response_body)
    READ_FROM_FILE = NO
    EVALUATED -> VariableSetter
Note: Extract results attribute
JSONExtractor_3
    EXTRACT_QUERY_TABLE = results JSON["results"]
    JSON_DOCUMENT = @Value(_response_body)
    READ_FROM_FILE = NO
    EVALUATED -> JSONFlattener
Note: Extract the URL pointing to the data. / Has to start with HTTPS and end with .csv
StringSearcher
    CASE = no
    MATCHED_RESULT_ATTR = _downloaddata
    REGEXP = https:.*\.csv
    STRING_TO_SEARCH = @Value(results_array)
    MATCHED -> Output (output)
Output (output)
ExpressionEvaluator
    ACTION = Overwrite Existing Attributes
    ATTRLIST = _JsonLength
    EXPRESSION = @Value(_JsonLength)+1

Bookmark: KEEP ASKING IF THE JOB HAS BEEN FINISHED ...
Note: Set a variable so we know when the job is done...
VariableSetter
    SCOPE = Global
    VALUE = TRUE
    VARNAME = keepChecking
    -> Cloner
Note: We going to try maximum 50 times...
Cloner
    COPIES = 50
    COPYATT = _copynum
    COPY -> VariableRetriever
Note: Read that same variable to evaluate if we still need to continue
VariableRetriever
    SCOPE = Global
    VALUE_ATTR = _keepChecking
    VARNAME = keepChecking
    -> TestFilter
TestFilter
    DEFAULT_VALUE = Done
    TEST_LIST = "BOOL_OP,OR,COMPOSITE_TEST,""""""1"""""",TEST_CLAUSE,TEST @Value(_keepChecking) = TRUE",KeepChecking
    KeepChecking -> Decelerator
Note: Wait for 3 seconds
Decelerator
    DECEL_TYPE = Per Feature Delay
    DELAY = 3
    -> DateTimeStamper_2
Note: Find indicator name from URL
StringSearcher_2
    CASE = no
    MATCHED_RESULT_ATTR = _indicator
    REGEXP = (?<=hidden-app-)[a-z,-]{1,}(?=-detail-web)
    STRING_TO_SEARCH = @Value(URl)
    MATCHED -> AttributeCreator_2
Note: Compile the queue URL
AttributeCreator_2
    ATTR_TABLE = SET_TO URl = https://cds.climate.copernicus.eu@Value(queue)?indicator=@Value(_indicator)&timestamp=@Value(_timestamp)
    -> HTTPCaller_2
Note: Poll if the server is ready with the calculation
HTTPCaller_2
    CONNECTION_TIMEOUT_LENGTH = 60
    ERROR_ATTR = _error
    FOLLOW_REDIRECTS = FOLLOW_WITH_GET
    HTTP_METHOD = GET
    REDIRECT_AUTH = ORIGINAL_DOMAIN_ONLY
    SAVE_FILE = Attribute
    STATUS_CODE_ATTR = _http_status_code
    TARGET_ATTR = _response_body
    TARGET_ATTR_ENCODING = auto-detect
    TARGET_URL = @Value(URl)
    TRANSFER_TIMEOUT_LENGTH = 90
    USE_COOKIES = No
    VERIFY_SSL_CERTIFICATES = Yes
    -> JSONExtractor_2
    <REJECTED> -> Logger
Note: Extract status attribute from JSON
JSONExtractor_2
    EXTRACT_QUERY_TABLE = status JSON["metadata"]["status"]
    JSON_DOCUMENT = @Value(_response_body)
    READ_FROM_FILE = NO
    EVALUATED -> TestFilter_2
Note: What status does the server bring back... only DONE will get out of the loop...
TestFilter_2
    DEFAULT_VALUE = <UNFILTERED>
    TEST_LIST = "BOOL_OP,OR,COMPOSITE_TEST,""""""1"""""",TEST_CLAUSE,TEST @Value(status) = RUNNING",RUNNING,"BOOL_OP,OR,COMPOSITE_TEST,""""""1"""""",TEST_CLAUSE,TEST @Value(status) = PENDING",PENDING,"BOOL_OP,OR,COMPOSITE_TEST,""""""1"""""",TEST_CLAUSE,TEST @Value(status) = DONE",DONE
    DONE -> VariableSetter_2
Note: Job is done, set the variable as job done so we skip all other trials.
VariableSetter_2
    SCOPE = Global
    VALUE = FALSE
    VARNAME = keepChecking
    -> JSONExtractor_3

Bookmark: TimeStamp
DateTimeStamper_2
    DATETIME_ATTR = _timestamp
    INCLUDE_OFFSET = NO
    STAMP_TYPE = datetime
    TIMEZONE = local
    -> DateTimeConverter
DateTimeConverter
    DATETIME_ATTR = _timestamp
    OUT_FORMAT = %Y-%m-%dT%H:%M:%S
    PASSTHROUGH = NO
    REPAIR_INPUT = YES
    -> AttributeCreator_3
AttributeCreator_3
    ATTR_TABLE = SET_TO _timestamp = @Value(_timestamp)Z
    -> StringSearcher_2

Bookmark: Get the last record in the list.
Note: Extract results attribute into a LIST
JSONFlattener
    ERROR_LIST_ATTR = _json_error
    JSON_DOCUMENT = @Value(results)
    NEW_ATTRIBUTES = array{}
    READ_FROM_FILE = NO
    RECURSIVE = Yes
    -> ListElementCounter
Note: Find out how many we have in the list...
ListElementCounter
    CNT_ATTR = _element_count
    LIST_NAME = array{}
    -> ListIndexer
Note: Take the last one as this contains the download URL
ListIndexer
    INDEX = @Value(_element_count)-1
    LIST_ATTR = array{}
    PREFIX = results_
    -> AttributeRemover
Note: Remove all the rest
AttributeRemover
    LIST_ATTRS = array{}
    -> StringSearcher

Bookmark: SOMETHING WEND WRONG...
Logger
    LOG_FEATURE = LOG_ONLY
    MAXCOORDS = 20
    MAXFEATS = 20
    MESSAGE = Feature is:
    SEVERITY = INFO
    LOGGED -> Terminator
Terminator
    MESSAGE = Translation Terminated

FME custom transformer FileExistenceChecker
Description
This transformer checks if input file paths exist and routes features accordingly.
The transformer supports UNC path, Zip files(*.zip) and wildcards. 
Details
The transformer will check if the filename selected in InputPort exists or not. 
The path can be supplied from a parameter, a network share location, by selecting a filename or using wildcards. 
Notes
Multiple filenames are not supported
Path to file must exist (no missing folders in the path)
FTP paths are not supported
Input
Filename path to check if file exists.   
Parameters
Input ports
Input File Path: Full path to the file to check for existence.  
Output Ports
Exists:Features are output through this port if the file exists.   
_path: The attribute stores the path to the file.  
DoesNotExist:Features are output through this port if the file does not exists.   
_path: This attribute stores the path to the file.

Parameters:
- Input =   # Input File Path

Input (input)
    -> ParameterFetcher
ParameterFetcher
    ATTR_LIST = FEC_FullPath {$(Input)}
    -> PythonCaller
AttributeManager
    ATTR_TABLE = REMOVE FEC_exists
    -> Exists (output)
Exists (output)
AttributeManager_2
    ATTR_TABLE = REMOVE FEC_exists
    -> DoesNotExist (output)
DoesNotExist (output)

Bookmark: Check if File Exists
PythonCaller
    NEW_ATTRIBUTES = FEC_exists
    PYTHONSOURCE:
      import fmeobjects
      import glob
      import zipfile

      def processFeature(feature):

          # Get input path attribute
          fullpath=feature.getAttribute("FEC_FullPath")

          # Check if the file exists
          if glob.glob(fullpath):
              feature.setAttribute("FEC_exists","Yes")
              # if not, try checking inside a zip file
          else:
              fullpath = fullpath.replace("\\","/")
              idx = fullpath.find(".zip")
              if idx > -1:
                  zipPath = fullpath[:idx+4]
                  pathInZip = fullpath[idx+5:]    #i.e. .zip/
                  try:
                      with zipfile.ZipFile(zipPath, 'r') as f:
                          if isinstance(f.getinfo(pathInZip),zipfile.ZipInfo):
                              feature.setAttribute("FEC_exists","Yes")
                              return
                  except (KeyError, FileNotFoundError) as e:
                      pass
                  # not found in a zipfile or in filesystem - does not exist
                  feature.setAttribute("FEC_exists","No")
    PYTHONSYMBOL = processFeature
    -> AttributeRenamer
AttributeRenamer
    ATTR_TABLE = RENAME_SET_DEFAULT FEC_FullPath > _path
    -> Tester
Tester
    BOOL_OP = OR
    COMPOSITE_TEST = 1
    TEST_CLAUSE = TEST @Value(FEC_exists) = Yes
    TEST_MODE = TEST
    PASSED -> AttributeManager
    FAILED -> AttributeManager_2

FME custom transformer MakeFeaturesFromAttribute

Parameters:
- FEATERLIST =   # "" List of features
- MATCHED_RESULT_ATTR =   # Result Attribute

Input (input)
    -> StringSearcher
Note: Use it to expose the attribute for the user.
StringSearcher
    CASE = no
    MATCHED_RESULT_ATTR = $(MATCHED_RESULT_ATTR)
    REGEXP = " "
    STRING_TO_SEARCH = " "
    MATCHED -> AttributeCreator_13
    NOT_MATCHED -> AttributeCreator_13
AttributeCreator_13
    ATTR_TABLE:
      SET_TO _featurelist = $(FEATERLIST)
      SET_TO _attributename = $(MATCHED_RESULT_ATTR)
    -> AttributeSplitter
AttributeSplitter
    ATTR_NAME = _featurelist
    DELIMITER = ,
    DROP_EMPTY_PARTS = No
    LIST_NAME = __featurelist
    TRIM_OPTION = Both
    -> ListExploder
ListExploder
    ATTR_ACCUM_MODE = Merge List Attributes
    ATTR_CONFLICT_RES = Use List Attribute Values
    INDEX_ATTR = _element_index
    LIST_ATTR = __featurelist{}
    ELEMENTS -> AttributeCreator
AttributeCreator
    ATTR_TABLE = SET_TO @Value(_attributename) = @Value(__featurelist)
    -> AttributeRemover_8
AttributeRemover_8
    REMOVE_ATTRS = _element_index,__featurelist,_attributename,_featurelist
    -> Output (output)
Output (output)
